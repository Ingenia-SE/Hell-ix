# system requirements

## SY-001: The drone shall be able to fly in a controlled manner (Functional)
Controlled manner is defined as the ability of the drone to maintain stable flight conditions, maintain a specific altitude, and follow a predefined flight path with minimal deviation from the planned trajectory.
Controlled manner is further specified with the following numerical constraints:
- Altitude: The drone shall be able to maintain a specific altitude within a tolerance range of +/- 10cm.
- Stability: The drone shall maintain a stable flight pattern with minimal pitch, roll, and yaw deviations from the intended flight path, with a tolerance range of +/- 5 degrees.
- Trajectory: The drone shall be able to follow a predefined flight path with minimal deviation, within a tolerance range of +/- 20cm from the intended trajectory.

### SY-001.1: The drone shall be able to lift its own weight plus the components mounted (Functional)
To participate in the different races the drone shall fly on its own. In order to achieve this, it has to self-propel, so the motors shall provide the necessary power to lift its own weight and the components mounted.

### SY-001.2: The GCS shall be able to manipulate the drone manually in case of security threats or unexpected events (Functional)
In case of any security threats or unexpected events, the manual control system shall be used to ensure the safety of the drone and the surrounding environment. The manual control system should be able to control the drone's movement in various directions, including forward, backwards, left, right, up, and down. It should also be able to adjust the speed and altitude of the drone in response to the remote control signals.

### SY-001.3: The GCS shall be able to control the movement of the drone automatically (Functional)
In order to ensure the reliable and safe operation of the drone, it is necessary for the drone to have a control system that is capable of controlling the movement of the drone automatically. This means the drone shall be equipped with an automatic control system that can be remotely accessed and controlled through a remote control device.

### SY-001.6: A control algorithm shall run onboard the drone (Functional)
To enable autonomous operation, the drone shall be equipped with a control algorithm that runs onboard. This algorithm shall be responsible for processing sensory inputs and controlling the drone's movements based on programmed objectives.

### SY-001.4: The GCS should relay information about the status of the drone (Functional)
The GCS should be able to provide real-time feedback on the drone's status, including its location, altitude, battery life, and any potential errors or malfunctions. This feedback should be easily accessible and clearly displayed on the remote control device to ensure the user has complete awareness of the drone's status.

### SY-001.5: The drone shall have automatic lift-off and landing procedures (Functional)
The drone shall be designed with automatic lift-off and landing procedures to facilitate safe and efficient operation. The automatic lift-off procedure shall enable the drone to take off from a stationary position without requiring manual input from the operator. The automatic landing procedure shall enable the drone to land in a safe and controlled manner, without requiring manual input from the operator.

## SY-004: The drone shall be able to navigate autonomously (Functional)
The drone shall be designed and programmed with the ability to navigate autonomously, following a predefined path and avoiding possible obstacles.

### SY-004.1: The drone shall detect and avoid obstacles in its path (Functional)
The drone must be able to detect gate obstacles and pass though them

#### SY-004.1.1: The system shall detect obstacles using a camera mounted on the drone (Functional)
A camera shall be used to collect information about the surroundings of the drone. Specifically, information about object types, distance, angles, etc. shall be collected.

#### SY-004.1.2: The drone must react in time to obstacles in its path (Functional)
The complete process of capturing, sending, processing, receiving and reacting shall be performed sufficiently fast so that the drone shall not collide with obstacles in its path.

### SY-004.2: The drone shall be able to follow a target position (Functional)
The drone shall be equipped with a control system and sensors that enable it to track and follow a specified target position accurately and reliably. The control system shall be capable of interpreting and executing commands from the GCS, and shall be designed to ensure the safety of the drone and surrounding environment.

### SY-004.3: The GCS shall generate trajectories for the drone using Bezier curves (Functional)
The Ground Control System (GCS) shall have direct responsibility for controlling the movement of the drone. It shall generate a trajectory consisting of a set of target positions defined by Bezier curves, which shall be transmitted to the drone's control system for execution.

## SY-003: The battery installed in the drone shall be large enough to ensure the competition is completed (Functional)
The battery system equipped on the drone shall be sufficient to complete all tasks with no need for a recharge. Therefore, the battery capacity shall be sufficiently large.

### SY-003.1: At any moment during the competition, there should be at least two battery replacements for the drone (Functional)
During the competition, it should be required that the drone is equipped with a minimum of two replacement batteries, available at any moment. These batteries should be charged and ready for use, to ensure the uninterrupted operation of the drone throughout the competition.

## SY-002: The drone should have visual indications of its current status (Functional)
The drone should be designed with clear and easily visible visual indications of its current status. These indications should include information such as battery level, altitude, speed, and any active modes or commands. The visual indications should have high contrast and brightness and should be easily distinguishable from a distance. They should also be positioned in a way that is visible to the operator during operation, without obstructing the view of the drone or causing distractions.
