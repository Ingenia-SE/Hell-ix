# software requirements

## SO-001: The source code shall be traceable (Functional)
The source code shall be located in a repository so that changes can be tracked and previous versions are accessible.

## SO-002: The software shall be able to communicate the drone and the GCS (Functional)
A communications software shall be designed so that the drone can communicate with the GCS wirelessly in order to transfer the collected data by the sensors in the drone and receive instructions from the computer.

### SO-002.1: The control system shall have a fail-safe mechanism in case of connection loss (Functional)
The control system shall have a fail-safe mechanism that triggers when the connection between the drone and the GCS is lost or disrupted. This mechanism shall perform the last assigned task and remain in its current position.

### SO-002.2: The control system shall have an automatic landing mechanism in case of connection loss (Functional)
If the connection between the drone and the GCS is lost for a period of 30 seconds or longer, the drone shall initiate a controlled landing procedure. This procedure shall involve the drone descending slowly and vertically until it reaches the ground.

### SO-002.3: The control system shall cooperate to estimate the position of the drone (Functional)
Both the drone and the GCS estimate the position of the drone using sensor information, odometry and a mathematical model. The GCS compares the current drone estimate with its own to obtain deviations from the target.

### SO-002.4: The drone shall send images to the GCS (Functional)
The onboard computer shall not perform any image processing, sending captured images directly to the GCS for processing.

## SO-003: The software shall be able to process images (Functional)
A processing pipeline shall be created which takes images as inputs and produce obstacle detections as outputs. The detections shall then be processed into instructions for the drone to execute.

## SO-005: The software shall complete a control loop fast enough to ensure the reactivity of the drone (Functional)
In order to ensure the reactivity of the drone, the processing pipeline shall be as lightweight as possible by making use of optimizations and efficient technologies.

### SO-005.1: The software shall use a compiled programming language (Functional)
The programming language shall be compiled in order to minimize the latency between detection and the consequent instruction.

## SO-004: The GCS shall have access to battery status (Functional)
The drone shall be equipped with a battery monitoring system that continuously measures the battery's remaining charge level. This information shall be transmitted to the GCS, which shall provide real-time battery status updates to the user. The remote control system shall use this information to warn the user when the battery level is low, allowing the user to take appropriate actions to ensure a safe landing and battery replacement if necessary.
