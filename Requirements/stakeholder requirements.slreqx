# stakeholder requirements

## ST-001: The system shall be functional before May 2023 (Informational)
According to the project management, the drone shall be able to perform both race phases by May 2023. This will be the end of the INGENIA SE Project and the competition will take place.

## ST-002: The drone shall fly in an enclosed space inside the university (Informational)
In order to meet the legal constraints, the drone shall fly inside the university area and below a specific height. Also, the space shall be enclosed to ensure the drone's stability and avoid severe atmospheric disturbances that could damage the drone because of its lightweight.

### ST-002.1: The system shall comply to current regulations on drone flights (Functional)
The drone shall comply with the following regulations:
- Reglamento de Ejecución 2020/746
- Real Decreto 1036/2017
- Reglamento Delegado 2019/945
- Reglamento de Ejecución 2019/947

## ST-003: The team shall design a competition in coordination with the other team (Functional)
The team shall negotiate with the other team the trials and rules of the competition, as well as the winning conditions.

### ST-003.1: The competition should have a speed test (Functional)
The test should accurately measure the flying speed of the drone.

### ST-003.2: The competition should have a precision test (Functional)
The test should measure the ability for the drone to detect a mark and position itself relative to that position precisely.

### ST-003.3: The competition should have an obstacle avoidance test (Functional)
The test should comprise obstacles to test the ability of the drone to detect and avoid those obstacles.

### ST-003.4: The competition should have a point system (Functional)
To determine the champion of the competition, a scoring system should be designed with defined scoring criteria for each test. The scoring mechanism should evaluate the performance of each team and assign a numerical value to their results. The team with the highest cumulative score at the end of the competition will be declared the winner.

### ST-003.5: The competition should value style (Functional)
A jury shall be responsible for determining the drone with the most stylish design and/or impressive control tricks, based on visual aesthetics and performance during the competition. The jury shall be composed of experts in the field of drone design and operation (Ricardo Sanz), with knowledge and experience in evaluating the technical and aesthetic aspects of drone performance.
